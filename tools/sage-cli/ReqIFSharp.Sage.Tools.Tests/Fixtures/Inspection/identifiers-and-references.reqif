# Specification: Toaster

## req-a (Requirement)
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- link -> req-c

## R5 (Requirement)

## req-unknown-type

## req-wrong-kind (Specification)

# Specification: Heating element

## req-b (Requirement)

# Specification: Crumb tray

## req-c (Requirement)

## R4: nameless toast (Requirement)

## req-orphan (Requirement)
