# Desk lamp requirements

# Specification: Desk lamp

## req-ok-object
Front view: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

## req-text-direct
The lamp shall glow.

## req-script
Blink

## req-class
The lamp shall be dimmable.

## R5
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
## R6
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
## R7
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
## R8
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
## req-simplified
Simplified text.

## R10
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
## R11
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
## req-heading
Lamp

## req-margin
Indented.
