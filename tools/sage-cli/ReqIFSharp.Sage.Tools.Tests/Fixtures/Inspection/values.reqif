# Kettle requirements

# Specification: Kettle

## req-values
- Code: far too long
- Code: ok
- Capacity: 11
- Fill ratio: 1.5
- Colour: red, green
- Other code: x

## req-more-values
- Fill ratio: 0.25
- Colour: small
- Capacity: 5
