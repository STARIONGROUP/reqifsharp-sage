# Coffee machine requirements

# Specification: Coffee machine
- ReqIF.Name: Coffee machine

## CM-1
The machine shall brew a cup of coffee.
- Cups per hour: 40
- Temperature tolerance: 0.5
- Safety relevant: true
- Reviewed on: 2026-01-10T09:00:00+01:00
- Priority: High

### CM-2
The machine shall grind the beans before brewing.
- refines -> CM-1
